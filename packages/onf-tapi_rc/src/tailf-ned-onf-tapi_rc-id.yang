module tailf-ned-onf-tapi_rc-id {
  namespace "http://tail-f.com/ned/onf-tapi_rc-id";
  prefix onf-tapi_rc-id;

  import tailf-ncs-ned {
    prefix ned;
  }

  identity onf-tapi_rc {
    base ned:generic-ned-id;
  }
}
