module tailf-ned-onf-tapi_rc-meta {
  namespace "http://tailf.com/ned/onf-tapi_rc/meta";
  prefix onf-tapi_rc-meta;

  import tailf-ncs {
    prefix ncs;
  }

  import tailf-common {
    prefix tailf;
  }

  import ietf-inet-types {
    prefix inet;
  }

  // This import is required when building for CDM style NSOs
  // Is automatically removed by the NED build system when
  // building for old style NSOs
  import onf-tapi_rc-gen {
    prefix family;
  }

  revision 2020-08-27 {
    description
      "1.0.0
       See CHANGES";
  }

  grouping ssl-settings {
    container ssl {
      tailf:info "Use SSL for connections towards the RESTCONF device";
      leaf accept-any {
        tailf:info "Accept any certificate (unsafe)";
        description
          "Accept any SSL certificate presented by the device.
          Warning! This enables Man in the Middle attacks and
          should only be used for testing and troubleshooting.";
        type boolean;
      }
    }
  }

  grouping ssl-certificate-settings {
    leaf certificate {
      tailf:info "Use specific DER formated SSL certificate";
      description
        "SSL certificate stored in DER format but since it is entered
          as Base64 it is very similar to PEM but without banners like
          \"----- BEGIN CERTIFICATE -----\".

          Default uses the default trusted certificates installed in
          Java JVM.

          An easy way to get the PEM of a server:
            openssl s_client -connect HOST:PORT
          ";
      type binary;
    }
  }

  grouping connection-settings {
    container connection {
      container authentication {
        tailf:info "Configure authentication method to use when the NED interacts with the RESTCONF device";
        leaf method {
          type enumeration {
            enum "basic";
            enum "none";
          }
          default "basic";
        }
      }
      uses ssl-settings;
    }
  }

  grouping restconf-settings {
    container restconf {
      tailf:info "Settings related to the RESTCONF API";
      leaf url-base {
        tailf:info "Device RESTCONF API URL base";
        description "API base URL for device REST API";
        type union {
          type enumeration {
            tailf:info "Let the NED auto probe for the correct URL base";
            enum "auto";
          }
          type string;
        }
        default "/restconf";
      }
      leaf update-method {
        tailf:info "RESTCONF method to use when updating config on the device.";
        type enumeration {
          enum "patch";
          enum "put";
        }
        default "patch";
      }
      leaf model-discovery {
        tailf:info "Configure the NED to auto probe for models supported by the device";
        type enumeration {
          enum "enabled";
          enum "disabled";
        }
        default "enabled";
      }
      leaf get-list-entries-separately {
        tailf:info "Configure the NED to get config in top level lists entry by entry instead of the whole list in one big fetch.";
        type boolean;
        default false;
      }
      container deviations {
        tailf:info "Settings related to deviations in the RESTCONF API for certain devices";
        // Add NED settings to controlling device specific adaptions here.
        leaf drop-connectivity-service-uuid {
          tailf:info "Remove the uuid tag below the connectivity-service from the outgoing JSON POST request.";
          type boolean;
          default false;
        }
        leaf dummy {
          // Workaround for an issue in the NedSettings class.
          // Can be removed if other leaves are defined in this container.
          tailf:hidden all;
          type empty;
        }
      }
    }
  }

  grouping trans-id-method-grouping {
    leaf trans-id-method {
      tailf:info "Configure how the NED shall calculate the transaction id. "
        +"Typically used after each commit and for check-sync operations";
      type enumeration {
        enum "last-modified-timestamp" {
          tailf:info "Use the 'Last-Modified' http header in the response" +
            " from a RESTCONF GET call. Use this setting only with devices that supports it.";
        }
        enum "disabled" {
          tailf:info "Disable the calculation of transaction id completely.";
        }
      }
      default "disabled";
    }
  }


  grouping live-status-ttl-settings {
    container live-status {
      tailf:info "Configure NED settings related to live-status.";
      leaf time-to-live {
        tailf:info "Define time-to-live for data fetched from the device"
          +" via live-status.(default 50)";
        type int32;
        default 50;
      }
    }
  }
  
  grouping log-verbose-grouping {
    leaf log-verbose {
      tailf:info "Enabled extra verbose logging in NED (for debugging)";
      default "false";
      type boolean;
    }
  }

  /// ========================================================================
  /// ned-settings
  /// ========================================================================

  augment "/ncs:devices/ncs:global-settings/ncs:ned-settings" {
    container onf-tapi_rc {
      uses connection-settings;
      uses live-status-ttl-settings;
      uses log-verbose-grouping;
      uses restconf-settings;
      uses trans-id-method-grouping;
    }
  }

  augment "/ncs:devices/ncs:profiles/ncs:profile/ncs:ned-settings" {
    container onf-tapi_rc {
      uses connection-settings;
      uses live-status-ttl-settings;
      uses log-verbose-grouping;
      uses restconf-settings;
      uses trans-id-method-grouping;
    }
  }

  augment "/ncs:devices/ncs:device/ncs:ned-settings" {
    // Different 'when' expressions used when building for NSOs with and without CDM support.
    // The NED build system will automatically 'uncomment' the right one.
    //
    // CDM style syntax:
    //when "derived-from(../ncs:device-type/ncs:generic/ncs:ned-id,'family:onf-tapi_rc-gen')";
    //
    // Old style syntax:
    //when "../ncs:device-type/ncs:generic/ncs:ned-id = 'onf-tapi_rc-id:onf-tapi_rc'";
    container onf-tapi_rc {
      uses connection-settings {
        augment "connection/ssl" {
          uses ssl-certificate-settings;
        }
      }
      uses live-status-ttl-settings;
      uses log-verbose-grouping;
      uses restconf-settings;
      uses trans-id-method-grouping;
    }
  }
}
