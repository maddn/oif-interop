module oif-tapi {

  namespace "http://example.com/oif-tapi";
  prefix oif-tapi;

  import ietf-inet-types {
    prefix inet;
  }
  import tailf-common {
    prefix tailf;
  }
  import tailf-ncs {
    prefix ncs;
  }
  import tapi-topology {
    prefix tapi-topology;
  }
  import tapi-connectivity {
    prefix tapi-connectivity;
  }
  import tapi-photonic-media {
    prefix tapi-photonic-media;
  }
  import tapi-odu {
    prefix tapi-odu;
  }

  description
    "Bla bla...";

  revision 2016-01-01 {
    description
      "Initial revision.";
  }

  container oif-tapi {
    description "This is an RFS skeleton service";

    list device {
      key name;
      leaf name {
        type leafref {
          path "/ncs:devices/ncs:device/ncs:name";
        }
      }

      container topology-context {
        config false;
        uses tapi-topology:topology-context;
        description "Augments the base TAPI Context with TopologyService information";

        tailf:action get {
          tailf:actionpoint get-topology-context;
          input {
            leaf strict-yang-check {
              type boolean;
              default false;
            }
          }
        }
      }
    }
  }

  augment "/oif-tapi:oif-tapi/oif-tapi:device/oif-tapi:topology-context/oif-tapi:topology/oif-tapi:node/oif-tapi:owned-node-edge-point" {
    container cep-list {
      uses tapi-connectivity:cep-list;
    }
    container media-channel-node-edge-point-spec {
      uses tapi-photonic-media:media-channel-node-edge-point-spec;
    }
    container odu-node-edge-point-spec {
      uses tapi-odu:odu-node-edge-point-spec;
    }
  }

  augment "/oif-tapi:oif-tapi/oif-tapi:device/oif-tapi:topology-context/oif-tapi:topology/oif-tapi:node/oif-tapi:owned-node-edge-point/oif-tapi:cep-list/oif-tapi:connection-end-point" {
    container otsi-connection-end-point-spec {
      uses tapi-photonic-media:otsi-connection-end-point-spec;
    }
    container otsi-assembly-connection-end-point-spec {
      uses tapi-photonic-media:otsi-assembly-connection-end-point-spec;
    }
    container media-channel-connection-end-point-spec {
      uses tapi-photonic-media:media-channel-connection-end-point-spec;
    }
    container ots-connection-end-point-spec {
      uses tapi-photonic-media:ots-connection-end-point-spec;
    }
    container media-channel-assembly-spec {
      uses tapi-photonic-media:media-channel-assembly-spec;
    }
    container odu-connection-end-point-spec {
      uses tapi-odu:odu-connection-end-point-spec;
    }
  }
}
